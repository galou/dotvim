# Longer, detailed macro description

__Name__ = ''
__Comment__ = ''
__Author__ = ''
__Version__ = ''
__Date__ = 'YYYY-MM-DD'
__License__ = 'LGPL-2.0-or-later'
__Web__ = 'http://forum.freecadweb.org/viewtopic.php?f=?&t=????'
__Wiki__ = 'http://www.freecadweb.org/wiki/Macro_Title_Of_macro'
__Icon__ = ''
__Help__ = ''
__Status__ = ''
__Requires__ = 'FreeCAD ?.??'
__Communication__ = 'https://github.com/FreeCAD/FreeCAD-macros/issues/'
__Files__ = ''

import FreeCAD as app

import FreeCADGui as gui
